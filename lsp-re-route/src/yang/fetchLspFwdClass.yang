module fetchLspFwdClass {

  namespace "http://example.com/fetchLspFwdClass";
  prefix fetchLspFwdClass;

  import ietf-inet-types {
    prefix inet;
  }
  import tailf-common {
    prefix tailf;
  }
  import tailf-ncs {
    prefix ncs;
  }

  description
    "Bla bla...";

  revision 2016-01-01 {
    description
      "Initial revision.";
  }

  list fetchLspFwdClass {
    description "This is an RFS skeleton service";

    key name;
    leaf name {
      tailf:info "Unique service id";
      tailf:cli-allow-range;
      type string;
    }


    // may replace this with other ways of refering to the devices.
    leaf-list device {
      type leafref {
        path "/ncs:devices/ncs:device/ncs:name";
      }
    }
}

  container fetch {   
    tailf:action fetchLspFwdClass {
      tailf:actionpoint fetchAction;
   	input {
		leaf forwardClass{
			type enumeration {
                		enum all;
                		enum non-zero;
			}
                        default "all";
		}
   	}
   output {
    list lspClasses {
      key "deviceName te_name";

	leaf deviceName {
	   type  string;
	    }

	leaf te_name {
	   type string;		
	   }

	leaf forwardClass {
	   type string;
	   }
	 }
      }
    }
  }
}
