module portal-network-model-generator {

  namespace "http://cisco.com/ns/wae/opm/portal-network-model-generator";

  prefix "portal-network-model-generator";

  import ietf-yang-types { prefix yang; }
  import tailf-common    { prefix tailf; }
  import tailf-ncs       { prefix ncs; }
  import cisco-wae       { prefix wae; }

  organization "Cisco Systems";

  description
   "This is a python OPM module for generating plan file that has both Interface Delay/latecny and Reservable Bandwidth utilization updated";

  revision 2017-02-24 {
   description
    "First release.";
  }

  grouping config-opm-status {
    container status {
      leaf active {
        tailf:info "True if the OPM is active";
        type boolean;
      }
      leaf last-run {
        tailf:info "Timestamp when the OPM was invoked last";
        type yang:date-and-time;
      }
      leaf last-successful-run {
        tailf:info "Timestamp of the OPM's last successful run";
        type yang:date-and-time;
      }
    }
  }

  grouping config-opm-input {
    leaf update {
          tailf:info "Updates Portal network model with delays or resv-bw or both";
          mandatory true;
          type enumeration {
            enum delays;
            enum resv-bw;
            enum both;
          }
      }
  }

  grouping config-opm-output {
  }
  augment "/wae:networks/wae:network/wae:opm" {
    container portal-network-model-generator {
      tailf:info "A python OPM module for generating plan file having both Interface Delay/latecny and Reservable Bandwidth utilization updated";

      uses config-opm-status;

      tailf:action run {
        tailf:actionpoint portal-network-model-generator-action-point;
        input {
          uses config-opm-input;
        }
        output {
          uses config-opm-output;
        }
      }
    }
  }
}
