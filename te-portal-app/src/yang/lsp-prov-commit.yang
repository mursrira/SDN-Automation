module lsp-prov-commit {

	namespace "http://cisco.com/ns/wae/opm/lsp-prov-commit";

	prefix "lsp-prov-commit";
	import ietf-inet-types { prefix inet; }
	import ietf-yang-types { prefix yang; }
	import tailf-common    { prefix tailf; }
	import tailf-ncs       { prefix ncs; }
	import cisco-wae       { prefix wae; }

	organization "Cisco Systems";

	description
		"This is a python OPM skeleton module.";

	revision 2017-06-08 {
		description
			"First release.";
	}

	grouping config-opm-input {
		leaf network-name {
		      tailf:info "Name of the network";
		      type leafref {
			      path "/wae:networks/wae:network/wae:name";
		      }
		}
		leaf source {
			tailf:info "Name of the source node";
	      		type leafref {
		      		path "/wae:networks/wae:network[wae:name=current()/../network-name]/wae:model/wae:nodes/wae:node/wae:name";	
	      		}
		}
		leaf lsp-name {
			tailf:info "Name of the lsp";
      			type string;
		}
		leaf destination {
			tailf:info "Name of the destination node";
      			type leafref {
	      			path "/wae:networks/wae:network[wae:name=current()/../network-name]/wae:model/wae:nodes/wae:node/wae:name";
      			}

		}
		leaf tunnel-id {
			tailf:info "Tunnel id";
      			type uint32;
		}
		leaf auto-route {
            		tailf:info "Auto route to be set / not set";
			type boolean;
			default false;
		}
		leaf action-type {
            		tailf:info "action-type (commit or dry-run)";
			type enumeration {
            	enum dry-run;
            	enum commit;
          	}
			default "dry-run";
		}
		/*leaf setup-pri {
			tailf:info "Setup priority";
      			type uint32;
		}
		leaf hold-pri {
			tailf:info "Hold priority";
      			type uint32;
		}*/
		list lsp-path {
			key path-option;
			leaf path-option {
				tailf:info "Path option number";
      				type uint16;
			}
			list hop {
				key step;
				
				leaf step {
                    			tailf:info "Step for the hop";
					type uint16;
				}
				leaf hop-node {
                    			tailf:info "Name of the remote node";
					type leafref {
						path "/wae:networks/wae:network[wae:name=current()/../../../network-name]/wae:model/wae:nodes/wae:node/wae:name";
					}
				}
                        	leaf hop-if {
                                	tailf:info "remote interface of node";
                                	type string;
				}
				leaf hop-ip {
                                        tailf:info "remote IP address of node";
                                        //type inet:ipv4-address;
                                        type string;
                                } 		

			}	
		}

	}

	grouping config-opm-output {
		leaf result {
			tailf:info "Boolean flag for status of lsp configuration";
      			type boolean;
      			default false;
		}
        
		leaf message {
			tailf:info "Output string for lsp config details";
      			type string;
		}
	}

augment "/wae:networks/wae:network/wae:opm" {
	container lsp-prov-commit {
		tailf:info "Lsp provisioning(commit) action module";
		tailf:action run {
			tailf:actionpoint lsp-prov-commit-point;
      		input {
	       		uses config-opm-input;
      		}
      		output {
	    		uses config-opm-output;
      		}
      	}
	}
 }
}
