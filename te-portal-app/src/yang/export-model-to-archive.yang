module export-model-to-archive {

  namespace "http://cisco.com/ns/wae/opm/export-model-to-archive";

  prefix "export-model-to-archive";
  
  import lsp-common	 { prefix lsp-common; }
  import ietf-yang-types { prefix yang; }
  import tailf-common    { prefix tailf; }
  import tailf-ncs       { prefix ncs; }
  import cisco-wae       { prefix wae; }

  organization "Cisco Systems";

  description
   "This is a python OPM module tosave WAE network model to archive";

  revision 2017-02-24 {
   description
    "First release.";
  }

  grouping config-opm-status {
    container status {
      leaf active {
        tailf:info "True if the OPM is active";
        type boolean;
      }
      leaf last-run {
        tailf:info "Timestamp when the OPM was invoked last";
        type yang:date-and-time;
      }
      leaf last-successful-run {
        tailf:info "Timestamp of the OPM's last successful run";
        type yang:date-and-time;
      }
    }
  }

  grouping config-opm-input {
    leaf flag {
      tailf:info "A sample input boolean flag";
      type boolean;
      default false;
    }
    leaf value {
      tailf:info "A sample input string";
      type string;
    }
  }

  grouping config-opm-output {
  }

  augment "/wae:networks/wae:network/wae:opm" {
    container export-model-to-archive {
      tailf:info "A python OPM module to export WAE network model to archive";

      uses config-opm-status;

      tailf:action run {
        tailf:actionpoint export-model-to-archive-action-point;
        input {
          uses config-opm-input;
        }
        output {
          uses config-opm-output;
        }
      }
    }
  }
}
